FME workspace Update 3vG mosaics.fmw

geospatialnapsa01: PythonCreator [off]
    NEW_ATTRIBUTES = srcfile srcpath
    PYTHONSOURCE_NEW:
      import fmeobjects
      import glob
      import os

      class FeatureCreator(object):
          """Template Class Interface:
          When using this class, make sure its name is set as the value of the 'Class
          to Process Features' transformer parameter.
          """

          def __init__(self):
              """Base constructor for class members."""
              pass

          def input(self, feature):
              src = r"\\geospatialnapsa01.file.core.windows.net\insar"
              # Init lists
              srcfiles=[]
              dstfiles=[]

              # Get files in src folder
              for path in glob.glob(src +  "\\**\\*WebMer.tif", recursive=True):
                  file = os.path.basename(path)
                  if int(file[0:4]) > 2017:
                      srcfiles.append(path)


              for path in srcfiles:
                  file = os.path.basename(path)
                  newFeature = fmeobjects.FMEFeature()
                  newFeature.setAttribute('srcfile', file)
                  newFeature.setAttribute('srcpath', path)
                  self.pyoutput(newFeature)

          def close(self):
              """This method is called at the end of the class."""
              pass
    PYTHONSYMBOL = FeatureCreator
    -> FeatureJoiner [LEFT]
FeatureJoiner [off]
    ATTR_CONFLICT_RES = Use Left
    GEOMETRY_HANDLING = Use Left
    JOIN_KEYS = srcfile srcfileold AUTO
    JOIN_MODE = Inner

Bookmark: New Bookmark
fmi_com: PythonCreator
    NEW_ATTRIBUTES = srcfileold srcpathold srcdir
    PYTHONSOURCE_NEW:
      import fmeobjects
      import glob
      import os

      class FeatureCreator(object):
          """Template Class Interface:
          When using this class, make sure its name is set as the value of the 'Class
          to Process Features' transformer parameter.
          """

          def __init__(self):
              """Base constructor for class members."""
              pass

          def input(self, feature):
              src = r"\\fmi.com\data\PHX\GMX_InSAR\InSAR_from_3vG"
              # Init lists
              srcfiles=[]
              dstfiles=[]

              # Get files in src folder
              for path in glob.glob(src +  "\\**\\*WebMer.tif", recursive=True):
                  file = os.path.basename(path)
                  if int(file[0:4]) > 2017:
                      srcfiles.append(path)


              for path in srcfiles:
                  file = os.path.basename(path)
                  srcdir = os.path.dirname(path)
                  newFeature = fmeobjects.FMEFeature()
                  newFeature.setAttribute('srcfileold', file)
                  newFeature.setAttribute('srcpathold', path)
                  newFeature.setAttribute('srcdir', srcdir)
                  self.pyoutput(newFeature)

          def close(self):
              """This method is called at the end of the class."""
              pass
    PYTHONSYMBOL = FeatureCreator
    -> FeatureJoiner_2 [LEFT]
Read_dest: PythonCreator
    NEW_ATTRIBUTES = dstfile dstpath dstdir
    PYTHONSOURCE_NEW:
      import fmeobjects
      import glob
      import os

      class FeatureCreator(object):
          """Template Class Interface:
          When using this class, make sure its name is set as the value of the 'Class
          to Process Features' transformer parameter.
          """

          def __init__(self):
              """Base constructor for class members."""
              pass

          def input(self, feature):
              dst = r"\\gisoneviewent-img\Imagery2\Orthoimagery"
              # Init lists
              srcfiles=[]
              dstfiles=[]

              # Get files in src folder
              for path in glob.glob(dst +  "\\**\\*WebMer.tif", recursive=True):
                  file = os.path.basename(path)
                  #if int(file[0:4]) > 2017:
                  dstfiles.append(path)


              for path in dstfiles:
                  file = os.path.basename(path)
                  dstdir = os.path.dirname(path)
                  newFeature = fmeobjects.FMEFeature()
                  newFeature.setAttribute('dstfile', file)
                  newFeature.setAttribute('dstpath', path)
                  newFeature.setAttribute('dstdir', dstdir)
                  self.pyoutput(newFeature)

          def close(self):
              """This method is called at the end of the class."""
              pass
    PYTHONSYMBOL = FeatureCreator
    -> FeatureJoiner_2 [RIGHT]
FeatureJoiner_2
    ATTR_CONFLICT_RES = Use Left
    GEOMETRY_HANDLING = Use Left
    JOIN_KEYS = srcfileold dstfile AUTO
    JOIN_MODE = Inner
    UNJOINED_LEFT -> StringSearcher
    UNJOINED_LEFT -> StringSearcher_2
StringSearcher
    CASE = yes
    MATCHED_RESULT_ATTR = _first_match
    REGEXP = [A-Z]{3}
    STRING_TO_SEARCH = @Value(srcfileold)
    MATCHED -> AttributeCreator
StringSearcher_2
    CASE = yes
    MATCHED_RESULT_ATTR = _first_match
    REGEXP = GRS_HL
    STRING_TO_SEARCH = @Value(srcfileold)
    MATCHED -> AttributeCreator
AttributeCreator
    ATTR_TABLE:
      SET_TO site = FME_CONDITIONAL:DEFAULT_VALUE'_FME_NO_OP_'BOOL_OP;OR;COMPOSITE_TEST;1;TEST @Value(_first_match) = ABR'ElAbra'BOOL_OP;OR;COMPOSITE_TEST;1;TEST @Value(_first_match) = BAG'Bagdad'BOOL_OP;OR;COMPOSITE_TEST;1;TEST @Value(_first_match) = CHN'Chino'BOOL_OP;OR;COMPOSITE_TEST;1;TEST @Value(_first_match) = CMX'Climax'BOOL_OP;OR;COMPOSITE_TEST;1;TEST @Value(_first_match) = CVE'CerroVerde'BOOL_OP;OR;COMPOSITE_TEST;1;TEST @Value(_first_match) = GRS'PTFI'BOOL_OP;OR;COMPOSITE_TEST;1;TEST @Value(_first_match) = GRS_HL'PTFI'BOOL_OP;OR;COMPOSITE_TEST;1;TEST @Value(_first_match) = HEN'Henderson'BOOL_OP;OR;COMPOSITE_TEST;1;TEST @Value(_first_match) = MIA'Miami'BOOL_OP;OR;COMPOSITE_TEST;1;TEST @Value(_first_match) = MOR'Morenci'BOOL_OP;OR;COMPOSITE_TEST;1;TEST @Value(_first_match) = SAM'Safford'BOOL_OP;OR;COMPOSITE_TEST;1;TEST @Value(_first_match) = SAF'Safford'BOOL_OP;OR;COMPOSITE_TEST;1;TEST @Value(_first_match) = SIE'Sierrita'BOOL_OP;OR;COMPOSITE_TEST;1;TEST @Value(_first_match) = TYR'Tyrone'FME_NUM_CONDITIONS15___
      SET_TO dest_path = \\gisoneviewent-img\Imagery2\Orthoimagery\@Value(site)\ComSat\@Left(@Value(srcfileold),4)\@Left(@Value(srcfileold),4)_@Value(_first_match)_3vG_ComSat\@Value(srcfileold)
    -> Robocopy_Rasters
    -> AttributeCreator_Output
Robocopy_Rasters: PythonCaller
    NEW_ATTRIBUTES = dstdir
    PYTHONSOURCE:
      import fme
      import fmeobjects
      import os
      from os import path
      from subprocess import call

      class FeatureProcessor(object):
          """Template Class Interface:
          When using this class, make sure its name is set as the value of the 'Class
          to Process Features' transformer parameter.
          """

          def __init__(self):
              """Base constructor for class members."""
              pass

          def input(self, feature):
              dstdir = os.path.dirname(feature.getAttribute('dest_path'))
              feature.setAttribute("dstdir", dstdir)
              call(["robocopy", feature.getAttribute('srcdir'), dstdir, feature.getAttribute('srcfileold'),"/MT:128"])

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> AttributeCreator_2
AttributeCreator_2
    ATTR_TABLE = SET_TO mos_dataset = \\gisoneviewent-img\Imagery1\Orthoimagery_gdb\@Value(site)_Imagery.gdb\S_@Value(site)_3vG_Comsat
    -> PythonCaller
PythonCaller
    PYTHONSOURCE:
      import fme
      import fmeobjects
      import arcpy


      class FeatureProcessor(object):
          """Template Class Interface:
          When using this class, make sure its name is set as the value of the 'Class
          to Process Features' transformer parameter.
          """

          def __init__(self):
              """Base constructor for class members."""
              pass

          def input(self, feature):
              # Delete existing objects
              try:
                  arcpy.management.Delete("mosaic_layer")
              except Exception as e:
                  print(f"Exception! {e}")

              # Add new rasters to mosaic dataset
              print(f"Adding {feature.getAttribute('srcfileold')} to mosaic dataset")
              arcpy.AddRastersToMosaicDataset_management(feature.getAttribute('mos_dataset'),
              					   "RASTER DATASET",
              					   feature.getAttribute('dest_path'),
              					   "UPDATE_CELL_SIZES",
                                     "UPDATE_BOUNDARY",
                                     "NO_OVERVIEWS",
                                     -1,
                                     0,
                                     1500,
                                     '',
                                     '',
                                     "SUBFOLDERS",
                                     "EXCLUDE_DUPLICATES",
                                     "BUILD_PYRAMIDS",
                                     "NO_STATISTICS",
                                     "NO_THUMBNAILS",
                                     '',
                                     "NO_FORCE_SPATIAL_REFERENCE",
                                     "NO_STATISTICS",
                                     None,
                                     "NO_PIXEL_CACHE")

              # Create in memory layer for processing
              arcpy.management.MakeMosaicLayer(feature.getAttribute('mos_dataset'), "mosaic_layer")

              # Select features to process
              arcpy.management.SelectLayerByAttribute("mosaic_layer\Footprint", "NEW_SELECTION", "'Aquisition_Date' IS NULL", None)

              # Calculate 4 fields in the mosaic dataset
              print('calculating fields')
              site = feature.getAttribute('site')
              prov = "3vG"
              plat = "ComSat"
              arcpy.management.CalculateField("mosaic_layer", "Acquisition_Date", 'Mid($feature.Name,4,2)+"/"+Mid($feature.Name,6,2)+"/"+Left($feature.Name,4)', "ARCADE", '', "TEXT", "NO_ENFORCE_DOMAINS")
              arcpy.management.CalculateField("mosaic_layer", "Site_Name", "'" + site + "'", "ARCADE", '', "TEXT", "NO_ENFORCE_DOMAINS")
              arcpy.management.CalculateField("mosaic_layer", "Provider", "'" + prov + "'", "ARCADE", '', "TEXT", "NO_ENFORCE_DOMAINS")
              arcpy.management.CalculateField("mosaic_layer", "Platform", "'" + plat + "'", "ARCADE", '', "TEXT", "NO_ENFORCE_DOMAINS")

              # Mosaic dataset paths to fix, only needed if script is running from a different machine.
              paths_list = [["\\gisoneviewent-img\imagery1\Orthoimagery_gdb","F:\Orthoimagery_gdb"],
                      ["\\gisoneviewent-img\imagery1\Orthoimagery","F:\Orthoimagery"],
                      ["\\gisoneviewent-img\Imagery2\Orthoimagery","G:\Orthoimagery"]
                      ]
              paths_list.append([r"\\gisoneviewent-img\Imagery2\Orthoimagery" + "\\" + site + "\\Comsat", r"G:\Imagery2\Orthoimagery" + "\\" + site + "\\Comsat"])

              # Repair the mosaic paths using the paths_list above
              arcpy.management.RepairMosaicDatasetPaths(feature.getAttribute('mos_dataset'), paths_list)

              # Synchronize mosaic dataset
              print('Synchronizing dataset')
              arcpy.management.SynchronizeMosaicDataset(feature.getAttribute('mos_dataset'),
                                                '',
                                                "UPDATE_WITH_NEW_ITEMS",
                                                "SYNC_ALL",
                                                "UPDATE_CELL_SIZES",
                                                "UPDATE_BOUNDARY",
                                                "NO_OVERVIEWS",
                                                "NO_PYRAMIDS",
                                                "NO_STATISTICS",
                                                "NO_THUMBNAILS",
                                                "NO_ITEM_CACHE",
                                                "REBUILD_RASTER",
                                                "UPDATE_FIELDS",
                                                "Acquisition_Date;CenterX;CenterY;End_Date;GroupName;Platform;ProductName;Provider;Raster;Shape;Site_Name;Tag;ZOrder",
                                                "UPDATE_EXISTING_ITEMS",
                                                "IGNORE_BROKEN_ITEMS",
                                                "OVERWRITE_EXISTING_ITEMS",
                                                "NO_REFRESH_INFO",
                                                "NO_STATISTICS")



              try:
                  arcpy.management.Delete("mosaic_layer")
              except Exception as e:
                  print(f"Exception! {e}")
              print("That's all folks!")

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> PythonCaller_2_Output
PythonCaller_2_Output: Inspector
AttributeCreator_Output: Inspector
